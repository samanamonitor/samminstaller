A brief example of how a name is mapped to an OID using MIB files.

All ISO assigned OIDs are under 1

--------------------------------------------------------------------------------
Starting value: 1.
--------------------------------------------------------------------------------

SNMPv2-SMI DEFINITIONS ::= BEGIN

org            OBJECT IDENTIFIER ::= { iso 3 }
dod            OBJECT IDENTIFIER ::= { org 6 }
internet       OBJECT IDENTIFIER ::= { dod 1 }
private        OBJECT IDENTIFIER ::= { internet 4 }
enterprises    OBJECT IDENTIFIER ::= { private 1 }
--------------------------------------------------------------------------------
Thus, enterprises is 1.3.6.1.4.1
--------------------------------------------------------------------------------
FOKUS-MIB DEFINITIONS ::= BEGIN

IMPORTS
    MODULE-IDENTITY, enterprises
        FROM SNMPv2-SMI;

fokus MODULE-IDENTITY
    ::= { enterprises 12325 }
--------------------------------------------------------------------------------
Result: 1.3.6.1.4.1.12325
--------------------------------------------------------------------------------
BEGEMOT-MIB DEFINITIONS ::= BEGIN

IMPORTS
    fokus
        FROM FOKUS-MIB;

begemot MODULE-IDENTITY
    ::= { fokus 1 }
--------------------------------------------------------------------------------
Result: 1.3.6.1.4.1.12325.1
--------------------------------------------------------------------------------
BEGEMOT-PF-MIB DEFINITIONS ::= BEGIN
IMPORTS
    begemot
        FROM BEGEMOT-MIB;

begemotPf MODULE-IDENTITY
    ::= { begemot 200 }
--------------------------------------------------------------------------------
Result: 1.3.6.1.4.1.12325.200
--------------------------------------------------------------------------------
begemotPfObjects        OBJECT IDENTIFIER ::= { begemotPf 1 }
--------------------------------------------------------------------------------
Result: 1.3.6.1.4.1.12325.200.1
--------------------------------------------------------------------------------
pfStatus                OBJECT IDENTIFIER ::= { begemotPfObjects 1 }
--------------------------------------------------------------------------------
Result: 1.3.6.1.4.1.12325.200.1.1
--------------------------------------------------------------------------------
pfStatusRunning OBJECT-TYPE
    SYNTAX      TruthValue
    MAX-ACCESS  read-only
    STATUS      current
    DESCRIPTION
        "True if pf is currently enabled."
    ::= { pfStatus 1 }
--------------------------------------------------------------------------------
Result: 1.3.6.1.4.1.12325.200.1.1.1
But since values are indexed by an intance id, add another 0 after for this
single object. If it were a table with multiple options there would be different
values for .0, .1, etc. as with interfaces.
--------------------------------------------------------------------------------

# Showing just the names:
$ snmpget -M +/usr/share/snmp/mibs/ -v2c -c public 198.51.100.6 BEGEMOT-PF-MIB::pfStatusRunning.0
BEGEMOT-PF-MIB::pfStatusRunning.0 = INTEGER: true(1)

--------------------------------------------------------------------------------

# Showing the UCD style name notation:
$ snmpget -Ou -M +/usr/share/snmp/mibs/ -v2c -c public 198.51.100.6 BEGEMOT-PF-MIB::pfStatusRunning.0
enterprises.fokus.begemot.begemotPf.begemotPfObjects.pfStatus.pfStatusRunning.0 = INTEGER: true(1)

# Note that even "enterprises" here is shortened, it could also be .iso.org.dod.internet.private.enterprises.
# Further note that this format is not as reliable for queries, and is shown only for demonstration.

--------------------------------------------------------------------------------

# Showing the entire OID:
$ snmpget -On -M +/usr/share/snmp/mibs/ -v2c -c public 198.51.100.6 BEGEMOT-PF-MIB::pfStatusRunning.0
.1.3.6.1.4.1.12325.1.200.1.1.1.0 = INTEGER: true(1)

--------------------------------------------------------------------------------

Note that the result was interpreted based on the model, as a TruthValue, a
result of 1 was interpreted as 'true'.
